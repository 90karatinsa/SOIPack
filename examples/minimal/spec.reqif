## REQ-1-RFC
- FCC boot sequence requirements refined from hardware ICD.

## REQ-4-DER
- Derived requirement clarifying the aural alert tone duration.

## REQ-9-DER
- Derived logging requirement referencing ARP4754A traceability guidance.
